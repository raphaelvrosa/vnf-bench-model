submodule probers {
	belongs-to vnf-bd {
		prefix "probers";
	}

	grouping prober-base {
		leaf name { type string; }
		container parameters {
			description "parameters to trigger prober execution";
		}
		container metrics {
			description "metrics output from prober execution";
		}
	}

	grouping ping {
		uses prober-base {
		    refine name {
	        	default "ping";
	        }
			augment parameters {
				leaf target { type string; } 
			}
			augment metrics {
				leaf rtt_mean { type string; }
			}
		}
	}

	grouping iperf3 {
		uses prober-base {
		    refine name {
	        	default "iperf3";
	        }
			augment parameters {
				leaf client { type string; } 
				leaf server { type string; } 
				leaf port { type string; } 
				leaf protocol { type string; } 
				leaf duration { type string; } 
				leaf frame_size { type string; } 
				leaf rate { type string; }
			}
			augment metrics {
				leaf bits_per_second { type string; }
			}
		}
	}

	grouping prober {
		leaf id { type uint32; }
		leaf instances { type uint32; }
		choice type {
			case ping {
				container ping {
					uses ping;
				}
			}
			case iperf3 {
				container iperf3 {
					uses iperf3;
				}
			}
		}
	}
}
