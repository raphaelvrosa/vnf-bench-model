module vnf-bd {
    namespace "urn:ietf:params:xml:ns:yang:vnf-bd";
    prefix "vnf-bd";

    include "probers";
    include "listeners";

    organization "IETF/BMWG";
    contact "Manuel Peuster <peuster@mail.uni-paderborn.de>, Raphael Vicente Rosa <raphaelvrosa@gmail.com>";
    description "Yang model for a VNF Benchmark Descriptor (VNF-BD) in the scope of IETF/BMWG";

    revision "2019-03-13" {
        description "V0.2: Reviewed role, policies, connection-points, lifecycle workflows, resources";
    }

    revision "2019-02-28" {
        description "V0.1: First release";
        reference "https://datatracker.ietf.org/doc/draft-rosa-bmwg-vnfbench/"; 
    }

    typedef workflows {
        type enumeration {
            enum create {
                description "When calling the create workflow";
            }
            enum start {
                description "When calling the start workflow";
            }
            enum stop {
                description "When calling the stop workflow";
            }
            enum delete {
                description "When calling the delete workflow";
            }
            enum custom {
                description "When calling a custom workflow";
            }
        }
    }

    grouping targets {
        leaf id { type string; }
        leaf name { type string; }
        leaf version { type string; }
        leaf author { type string; }
        leaf description { type string; }
    }

    grouping tool {
        leaf id { type uint32; }
        leaf instances { type uint32; }
        list parameters { 
            key "input";
            leaf input { type string; }
            leaf value { type string; }
        }
        list metrics { 
            key "name";
            leaf name { type string; }
            leaf units { type string; }
        }
    }

    grouping agent {
        list probers {
            key "id";
            uses prober;

            /* Optional change to
            uses tool;
            */
        }
    }

    grouping monitor {
        container habitat { 
            leaf setting { type string; }
            leaf location { type string; }
            leaf target { type string; }
        }
        list listeners {
            key "id";
            uses listener;
            
            /* Optional change to 
            uses tool;
            */
        }
    }

    grouping role {
        leaf role { type string; }

        choice mode {
            case agent {
                uses agent;
            }
            case monitor {
                uses monitor;
            }
        }
    }

    grouping requirements {

        uses role;
        
        container resources {
            container cpu { 
                leaf vcpus { type uint32; }
                leaf cpu_bw { type string; }
                leaf pinning { type string; }
            }
            container memory { 
                leaf size { type uint32; }
                leaf units { type string; }
            }
            container storage { 
                leaf size { type uint32; }
                leaf units { type string; }
                leaf volumes { type string; }
            }
        }
    }  

    grouping connection_points {
        leaf id { type string; }
        leaf interface { type string; }
        leaf type { type string; }
        leaf address { type string; }
        leaf link-id { type string; }
        /*
        leaf link-id { 
            type leafref {
                path "../../../links/id";
            } 
        }
        */
    }

    grouping nodes {
        leaf id { type string; }
        leaf type { type string; }
        leaf image { type string; }
        leaf image_format { type string; }

        uses requirements;
        
        list connection_points {
            key "id";
            uses connection_points;
        }

        list lifecycle {
            key "workflow";
            leaf workflow {
                type workflows;
            }
            leaf name { 
                type string; 
                when "../workflow = 'custom'";
            }
            
            list parameters { 
                key "input";
                leaf input { type string; }
                leaf value { type string; }
            }
            leaf implementation { type string; }
        }
    
    }

    grouping links {
        leaf id { type uint32; }
        leaf name { type string; }
        leaf type { type string; }
        leaf network { type string; }
        /* leaf-list connection_points { type string; } */
    }

    grouping scenario {
        list nodes {
            key "id";
            uses nodes;
        }

        list links {
            key "id";
            uses links;
        }

        list policies {
            key "name";
            leaf name { type string; }
            leaf type { type string; }
            leaf targets { type string; }
            leaf action { type string; }
        }
    }

    grouping settings {
        leaf id { type string; }
        leaf name { type string; }
        leaf version { type string; }
        leaf author { type string; }
        leaf description { type string; }

        container experiment {
            leaf trials { type uint32; default 1; }
            leaf tests { type uint32; default 1; }
            leaf methods { type uint32; default 1; }
        }

        container environment {
            leaf name { type string; }
            leaf description { type string; }
            container plugin {
                leaf type { type string; }
                list parameters {
                    key "input";
                    leaf input { type string; }
                    leaf value { type string; }
                } 
            }
        }
    }

    grouping vnf-bd {
        description "Grouping for a single vnf-bd";

        uses settings;

        list targets {
            key "id";
            uses targets;
        }

        container scenario{
            uses scenario;
        }

    }

    container vnf-bd {
        uses vnf-bd;
    }
}
