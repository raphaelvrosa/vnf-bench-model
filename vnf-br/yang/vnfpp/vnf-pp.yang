module vnf-pp {
    namespace "urn:ietf:params:xml:ns:yang:vnf-pp";
    prefix "vnf-pp";

    organization "IETF/BMWG";
    contact "Manuel Peuster <peuster@mail.uni-paderborn.de>, Raphael Vicente Rosa <raphaelvrosa@gmail.com>";
    description "Yang model for a VNF Performance Profile (VNF-PP) in the scope of IETF/BMWG";

    revision "2019-10-15" {
        description "Reviewed VNF-PP structure - defines reports, snapshots, evaluations";
        reference ""; 
    }

    revision "2019-08-13" {
        description "V0.1: First release";
        reference "https://datatracker.ietf.org/doc/draft-rosa-bmwg-vnfbench/"; 
    }

    grouping tuple {
        description "A tuple used as key-value.";
        leaf key { 
            type string; 
            description "Tuple key.";
        }
        
        leaf value { 
            type string; 
            description "Tuple value.";
        }
    }

    grouping settings {
        description "Settings of a single vnf-pp.";

        leaf id {
            type string;
            description "Unique identifier";    
        }
        leaf name {
            type string;
            description "Name of the experiment";    
        }
        leaf version {
            type string;
            description "Version of the experiment";
        }
        leaf author {
            type string;
            description "Author of the experiment";
        }
        leaf description {
            type string;
            description "Description of the experiment";    
        }
        leaf timestamp {
            type string;
            description "Time (date, hour, minute, second) when the vnf-pp was created.";    
        }
    }

    grouping metric {
        description "Metric that holds the recorded benchmarking results, can be
        a single value (scalar), a list of values (vector), or a list of key/value
        data(tuple-vector), e.g., for timeseries.";

        leaf name { 
            type string; 
            description "Metric name";    
        }
        
        leaf unit { 
            type string; 
            description "Unit of the metric value(s)";    
        }
        
        leaf type {
            type string;
            mandatory true;
            description "The data type encoded in the value.";
        }

        choice value {
            case scalar {
                leaf scalar {
                    type string;
                    mandatory true;
                    description "Single value";
                }
            }
            case vector {
                leaf-list vector {
                    type string;
                    min-elements 1;
                    description "List of values";
                }
            }
            case tuple-vector {
                list tuple-vector {
                    key "key";
                    uses tuple;
                    description "List of key/values e.g. timeseries.";
                }
            }
            mandatory true;
            description "Choice: scalar, vector, tupleg-vector";
        }
    }

    grouping evaluation {
        description "A set of metrics and their source associated with a single trial.";

        leaf id { 
            type string; 
            description "Unique id";
        }

        container source {
            description "Details regarding the source of the evaluation.";

            leaf id { 
                type string; 
                description "Unique source id";
            }
            
            leaf name { 
                type string; 
                description "Name of the source of the evaluation.";
            }

            leaf type { 
                type string; 
                description "Type of the evaluation source, i.e., prober or listener.";
            }
            
            leaf version { 
                type string; 
                description "Version of the tool interfacing the prober/listener.";
            }
            
            leaf call { 
                type string; 
                description "Full call realized by the source of evaluation.";
            }
        }

        container timestamp {
            description "Timestamps of the procedures that realized the extraction of the evaluation.";

            leaf start { 
                type string; 
                description "Time (date, hour, minute, second) when the evaluation started";
            }

            leaf stop { 
                type string; 
                description "Time (date, hour, minute, second) when the evaluation stopped";
            }
        }

        list metrics {
            key "name";
            uses metric;
            description "List of metrics obtained by evaluation.";
        }
    }


    grouping snapshot {
        description "Set of evaluations and their origin based on a single trial.";
        
        leaf id { 
            type string; 
            description "Unique identifier.";
        }
        
        leaf trial { 
            type uint32; 
            description "Trial identifier when the snapshot was obtained.";
        }

        container origin {
            description "Trial when the snapshot was obtained.";

            leaf id { 
                type string; 
                description "Unique origin identifier, i.e., agent or monitor identifier.";
            }

            leaf role { 
                type string; 
                description "Role of the component, origin of the snapshop, i.e., agent or monitor.";
            }
            
            leaf host { 
                type string; 
                description "Host name where the source of the snapshot was placed.";
            }
        }

        list evaluations {
            key "id";
            uses evaluation;
            description "List of evaluations contained in a single snapshot.";
        }
    }

    grouping report {
        description "Set of snapshots based on a single test.";

        leaf test { 
            type uint32; 
            description "Test identifier when the snapshot was obtained.";
        }
        
        list snapshots {
            key "id";
            uses snapshot;
            description "List of snapshots contained in a single report.";
        }
    }

    grouping vnf-pp {
        description "Grouping for a single vnf-pp.";

        uses settings;

        list reports {
            key "test";
            uses report;
            description "List of reports obtained in a vnf-pp.";
        }
    }

    container vnf-pp {
        uses vnf-pp;
        description "A VNF-PP.";
    }
}
